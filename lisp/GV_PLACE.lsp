;;; ==========================================================================
;;;  GV_PLACE.lsp -- place coordinate callouts at 174 points
;;;  Generated 2026-09-02 from all_gv_points.csv
;;;
;;;  Load with APPLOAD, then type:  GVPLACEPOINTS
;;; ==========================================================================

(vl-load-com)

;; ---- edit these if needed -------------------------------------------------

(setq *GV-BLOCK* "COOR XY")     ; attributed callout block
(setq *GV-SCALE* 1.608006)       ; its insertion scale
(setq *GV-ROT*   0.0000)         ; its rotation, degrees
(setq *GV-PREC*  3)        ; decimal places in the attribute text
(setq *GV-LABEL* nil)       ; T to also write the point name as text
(setq *GV-LAYER* "Text-Number") ; layer for that text
(setq *GV-HT*    1.500)       ; its height
(setq *GV-DX*    0.340)       ; where it sits relative to the point
(setq *GV-DY*    -3.906)

;; Leave these at 0 when the drawing is modelled on the survey grid. Set them
;; when the drawing sits in a local system, so E/N land in the right place.
(setq *GV-OFFE*  0.0)
(setq *GV-OFFN*  0.0)

;; ---- the coordinates ------------------------------------------------------

(setq *GV-POINTS* '(
  ("GV1"    478042.125 2744292.332)
  ("GV2"    477976.834 2744283.671)
  ("GV3"    477905.976 2744384.209)
  ("GV4"    477897.791 2744400.646)
  ("GV5"    477853.859 2744393.148)
  ("GV6"    477696.890 2744282.527)
  ("GV7"    477676.823 2744271.783)
  ("GV8"    477755.104 2744127.412)
  ("GV9"    477768.510 2744136.859)
  ("GV10"   477754.153 2744201.272)
  ("GV11"   477911.123 2744311.893)
  ("GV12"   477892.571 2744374.763)
  ("GV13"   477863.307 2744379.742)
  ("GV14"   477706.336 2744269.124)
  ("GV15"   477689.471 2744253.836)
  ("GV16"   477744.708 2744214.675)
  ("GV17"   477901.674 2744325.300)
  ("GV18"   477768.072 2744103.168)
  ("GV19"   477762.882 2744048.854)
  ("GV20"   477843.791 2744002.431)
  ("GV21"   477778.539 2744059.889)
  ("GV22"   477777.115 2744078.504)
  ("GV23"   477805.862 2744103.285)
  ("GV24"   477786.860 2744116.408)
  ("GV25"   477804.426 2744124.583)
  ("GV26"   477817.019 2744106.715)
  ("GV27"   478054.818 2744274.321)
  ("GV28"   478111.112 2744263.939)
  ("GV29"   478115.755 2744205.778)
  ("GV30"   477852.476 2743990.110)
  ("GV31"   477859.709 2743979.848)
  ("GV32"   477873.113 2743989.294)
  ("GV33"   477871.820 2744010.592)
  ("GV34"   478067.622 2744126.370)
  ("GV35"   478140.300 2744023.245)
  ("GV36"   478153.703 2744032.691)
  ("GV37"   478081.028 2744135.818)
  ("GV38"   478126.716 2744190.224)
  ("GV39"   478229.314 2744096.391)
  ("GV40"   478239.174 2744089.271)
  ("GV41"   478237.150 2744070.832)
  ("GV42"   478234.250 2744053.907)
  ("GV43"   478216.564 2744046.278)
  ("GV44"   477978.105 2743878.142)
  ("GV45"   477974.929 2743815.481)
  ("GV46"   478049.237 2743710.043)
  ("GV47"   478093.234 2743704.869)
  ("GV48"   478344.819 2743882.168)
  ("GV49"   478335.371 2743895.574)
  ("GV50"   478253.311 2743891.353)
  ("GV51"   478244.389 2743904.018)
  ("GV52"   478210.467 2743902.731)
  ("GV53"   478038.970 2743781.869)
  ("GV54"   478048.413 2743768.469)
  ("GV55"   478219.912 2743889.328)
  ("GV56"   478239.905 2743881.905)
  ("GV57"   478083.789 2743718.271)
  ("GV58"   478062.643 2743719.490)
  ("GV59"   477988.338 2743824.930)
  ("GV60"   477990.839 2743860.073)
  ("GV61"   478229.277 2744028.238)
  ("GV62"   478259.557 2744039.844)
  ("GV63"   478276.984 2744035.622)
  ("GV64"   478284.195 2744018.516)
  ("GV65"   478348.340 2743927.489)
  ("GV66"   478367.387 2743892.996)
  ("GV67"   478403.586 2743918.412)
  ("GV68"   478420.267 2743935.341)
  ("GV69"   478669.961 2744111.312)
  ("GV70"   478685.289 2744118.712)
  ("GV71"   478609.422 2744259.651)
  ("GV72"   478596.019 2744250.206)
  ("GV73"   478615.271 2744188.017)
  ("GV74"   478624.676 2744174.672)
  ("GV75"   478462.992 2744060.725)
  ("GV76"   478453.588 2744074.070)
  ("GV77"   478438.429 2744066.782)
  ("GV78"   478471.825 2744014.573)
  ("GV79"   478458.418 2744005.125)
  ("GV80"   478410.820 2743948.746)
  ("GV81"   478377.567 2743948.086)
  ("GV82"   478313.414 2744039.109)
  ("GV83"   478302.271 2744069.334)
  ("GV84"   478314.479 2744088.153)
  ("GV85"   478636.153 2744314.763)
  ("GV86"   478694.562 2744303.757)
  ("GV87"   478812.090 2744206.297)
  ("GV88"   478832.047 2744225.530)
  ("GV89"   479078.687 2744399.347)
  ("GV90"   479093.547 2744406.421)
  ("GV91"   479017.592 2744549.225)
  ("GV92"   479004.189 2744539.779)
  ("GV93"   479024.417 2744476.354)
  ("GV94"   479033.868 2744462.943)
  ("GV95"   478872.287 2744349.073)
  ("GV96"   478862.840 2744362.479)
  ("GV97"   478846.663 2744354.354)
  ("GV98"   478879.918 2744302.180)
  ("GV99"   478866.496 2744292.721)
  ("GV100"  478822.597 2744238.938)
  ("GV101"  478723.825 2744324.380)
  ("GV102"  478767.252 2744462.047)
  ("GV103"  478693.492 2744566.703)
  ("GV104"  478851.849 2744701.002)
  ("GV105"  478865.558 2744710.664)
  ("GV106"  478894.746 2744722.594)
  ("GV107"  478887.513 2744732.856)
  ("GV108"  478854.613 2744726.195)
  ("GV109"  478840.904 2744716.533)
  ("GV110"  478604.792 2744550.134)
  ("GV111"  478615.737 2744534.603)
  ("GV112"  478680.073 2744557.246)
  ("GV113"  478753.827 2744452.587)
  ("GV114"  478662.005 2744411.922)
  ("GV115"  478544.353 2744578.877)
  ("GV116"  478537.042 2744603.746)
  ("GV117"  478550.472 2744623.344)
  ("GV118"  478715.412 2744739.583)
  ("GV119"  478804.543 2744802.392)
  ("GV120"  478854.294 2744818.005)
  ("GV121"  478869.948 2744829.038)
  ("GV122"  478799.120 2744862.102)
  ("GV123"  478688.967 2744984.973)
  ("GV124"  478678.210 2744974.093)
  ("GV125"  478491.966 2744819.379)
  ("GV126"  478503.460 2744807.907)
  ("GV127"  478575.885 2744705.146)
  ("GV128"  478589.276 2744714.583)
  ("GV129"  478570.521 2744776.598)
  ("GV130"  478735.469 2744892.845)
  ("GV131"  478726.023 2744906.248)
  ("GV132"  478561.073 2744790.003)
  ("GV133"  478516.854 2744817.346)
  ("GV134"  478687.660 2744960.685)
  ("GV135"  478701.636 2744967.140)
  ("GV136"  478785.773 2744852.695)
  ("GV137"  478791.829 2744820.432)
  ("GV138"  478702.660 2744757.677)
  ("GV139"  478537.719 2744641.439)
  ("GV140"  478514.711 2744635.385)
  ("GV141"  478489.402 2744656.873)
  ("GV142"  478460.218 2744636.305)
  ("GV143"  478473.548 2744624.496)
  ("GV144"  478471.921 2744605.229)
  ("GV145"  478468.215 2744587.751)
  ("GV146"  478494.253 2744573.553)
  ("GV147"  478513.406 2744567.851)
  ("GV148"  478515.169 2744558.309)
  ("GV149"  478632.822 2744391.356)
  ("GV150"  478623.380 2744332.888)
  ("GV151"  478301.806 2744106.136)
  ("GV152"  478296.927 2744098.079)
  ("GV153"  478279.940 2744100.973)
  ("GV154"  478258.433 2744117.040)
  ("GV155"  478235.726 2744193.401)
  ("GV156"  478570.912 2744429.613)
  ("GV157"  478558.240 2744447.594)
  ("GV158"  478223.056 2744211.380)
  ("GV159"  478140.297 2744284.506)
  ("GV160"  478149.319 2744340.720)
  ("GV161"  478471.193 2744567.560)
  ("GV162"  478458.522 2744585.540)
  ("GV163"  478421.471 2744581.945)
  ("GV164"  478408.480 2744571.904)
  ("GV165"  478158.507 2744396.627)
  ("GV166"  478145.519 2744386.587)
  ("GV167"  478136.646 2744358.703)
  ("GV168"  477963.427 2744274.223)
  ("GV169"  478660.514 2744124.717)
  ("GV170"  478672.640 2744136.656)
  ("GV171"  479069.239 2744412.752)
  ("GV172"  479081.597 2744424.247)
  ("GV173"  478535.144 2744634.919)
  ("GV174"  477149.577 2744103.507)
))

;; ---- the work -------------------------------------------------------------

(defun gvp:attribs (e / out nx)
  "The ATTRIB entities belonging to an INSERT."
  (setq out nil nx (entnext e))
  (while (and nx (= "ATTRIB" (cdr (assoc 0 (entget nx)))))
    (setq out (cons nx out) nx (entnext nx)))
  (reverse out))

(defun gvp:place (name ex ny / p ns es obj a d tag)
  "Insert the callout at (ex ny) and write the coordinates into its attributes."
  (setq p  (list (+ ex *GV-OFFE*) (+ ny *GV-OFFN*) 0.0)
        ns (strcat "N=" (rtos ny 2 *GV-PREC*))
        es (strcat "E=" (rtos ex 2 *GV-PREC*)))
  ;; _non defeats running osnap, which would otherwise pull the block onto
  ;; whatever happens to lie near the point
  (command "._-INSERT" *GV-BLOCK* "_non" p *GV-SCALE* *GV-SCALE* *GV-ROT*)
  (setq obj (entlast))
  (foreach a (gvp:attribs obj)
    (setq d (entget a) tag (strcase (cdr (assoc 2 d))))
    (cond
      ((wcmatch tag "Y*,N*") (entmod (subst (cons 1 ns) (assoc 1 d) d)))
      ((wcmatch tag "X*,E*") (entmod (subst (cons 1 es) (assoc 1 d) d)))))
  (entupd obj)
  (if *GV-LABEL*
    (progn
      (if (not (tblsearch "LAYER" *GV-LAYER*))
        (entmakex (list '(0 . "LAYER") '(100 . "AcDbSymbolTableRecord")
                        '(100 . "AcDbLayerTableRecord") (cons 2 *GV-LAYER*)
                        '(70 . 0) '(62 . 7) (cons 6 "Continuous"))))
      (entmakex (list '(0 . "TEXT") '(100 . "AcDbEntity")
                      (cons 8 *GV-LAYER*) '(100 . "AcDbText")
                      (cons 10 (list (+ (car p) *GV-DX*) (+ (cadr p) *GV-DY*) 0.0))
                      (cons 40 *GV-HT*) (cons 1 name) '(50 . 0.0)))))
  obj)

(defun c:GVPLACEPOINTS ( / olde oldd oldc oldo n item)
  (if (not (tblsearch "BLOCK" *GV-BLOCK*))
    (progn
      (princ (strcat "\nBlock \"" *GV-BLOCK* "\" is not in this drawing."))
      (princ "\nInsert one copy of it first, then run this again."))
    (progn
      (setq olde (getvar "ATTREQ") oldd (getvar "ATTDIA")
            oldc (getvar "CMDECHO") oldo (getvar "OSMODE"))
      (setvar "ATTREQ" 0) (setvar "ATTDIA" 0)
      (setvar "CMDECHO" 0) (setvar "OSMODE" 0)
      (command "._UNDO" "_BEGIN")
      (setq n 0)
      (foreach item *GV-POINTS*
        (gvp:place (car item) (cadr item) (caddr item))
        (setq n (1+ n)))
      (command "._UNDO" "_END")
      (setvar "ATTREQ" olde) (setvar "ATTDIA" oldd)
      (setvar "CMDECHO" oldc) (setvar "OSMODE" oldo)
      (princ (strcat "\nPlaced " (itoa n) " callout(s) using \"" *GV-BLOCK* "\"."))
      (princ "\nOne UNDO reverses the whole run.")))
  (princ))

(princ (strcat "\nGV_PLACE.lsp loaded -- 174 points ready.  Type GVPLACEPOINTS"))
(princ)
